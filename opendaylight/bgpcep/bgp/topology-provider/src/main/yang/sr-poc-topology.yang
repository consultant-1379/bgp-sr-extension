module sr-poc-topology {
    yang-version 1;
    namespace "urn:TBD:params:xml:ns:yang:network:sr-poc-topology";
    prefix "sr";
    import network-topology {
        prefix nt;
        revision-date 2013-10-21;
    }
    import odl-bgp-topology-types {
        prefix bgp-tt;
        revision-date 2016-05-24;
    }

    import l3-unicast-igp-topology {
        prefix "l3t";
        revision-date 2013-10-21;
    }
    import ietf-inet-types {
        prefix inet;
        revision-date 2010-09-24;
    }
    import isis-topology {
        prefix isis;
        revision-date 2013-10-21;
    }

    import ospf-topology {
        prefix ospf;
        revision-date 2013-10-21;
    }

    organization "Ericsson AB";
    contact "TBD";

    description
       "Copyright (c)2014 Ericsson, AB. All rights reserved.

        This program and the accompanying materials are made available
        under the terms of the Eclipse Public License v1.0 which
        accompanies this distribution, and is available at
        http://www.eclipse.org/legal/epl-v10.html";

    revision "2014-11-12" {
        description "Initial version";
    }

   typedef uint24 {
       type uint32 {
         range "0..16777215";
       }
       description
         "24-bit unsigned integer.";
    }

    grouping prefix-sid {
        reference "https://tools.ietf.org/html/draft-ietf-isis-segment-routing-extensions-08#section-2.1";
        leaf flags {
            type bits {
                bit r {
                    position 0;
                }
                bit n {
                    position 1;
                }
                bit p {
                    position 2;
                }
                bit e {
                    position 3;
                }
               /*
                * flags v and l are not handled by the bgp-segment-routing.yang
                */
             }
        }
        leaf algorithm {
            type uint8;
        }
        leaf sid {
            description "Segment Identifier";
            type uint32;
        }
        leaf local-label {
            description "Local Label (SRGB minimum value)";
            type uint32;
        }
    }

    grouping unidirectional-linkdelay {
        leaf flags {
            type bits {
                bit a {
                    position 0;
                }
            }
        }
        leaf delay {
            type uint24 {
                range "0..16777215";
            }
        }
    }

    grouping next-hop {
        choice c-next-hop {
            case ipv4-next-hop-case {
                container ipv4-next-hop {
                    reference "http://tools.ietf.org/html/rfc4271#section-5.1.3";
                    leaf global {
                        type inet:ipv4-address;
                    }
                }
            }
            case ipv6-next-hop-case {
                container ipv6-next-hop {
                    reference "http://tools.ietf.org/html/rfc4760#section-3";
                    leaf global {
                        type inet:ipv6-address;
                    }
                    leaf link-local {
                        type inet:ipv6-address;
                    }
                }
            }
        }
    }

    grouping adj-sid {
        reference "https://tools.ietf.org/html/draft-previdi-isis-segment-routing-extensions-05#section-2.3.1";
        leaf flags {
            type bits {
                bit f {
                    position 0;
                }
                bit b {
                    position 1;
                }
            }
        }
        leaf weight {
            type uint8;
        }
        leaf type {
            type uint8;
        }
        leaf length {
            type uint8;
        }
        leaf sid {
            type uint32;
        }
        leaf local-label {
            description "Local Label (SRGB minimum value).";
            type uint32;
        }
    }

    augment "/nt:network-topology/nt:topology/nt:node/l3t:igp-node-attributes/l3t:prefix" {
        when "../../../nt:topology-types/bgp-tt:bgp-linkstate-topology-type" +
             " or ../../../nt:topology-types/l3t:l3-unicast-igp-topology";
        container prefix-sid{
            uses prefix-sid;
        }
        uses next-hop;
    }

    augment "/nt:network-topology/nt:topology/nt:link/l3t:igp-link-attributes/isis:isis-link-attributes/isis:ted" {
        when "../../../nt:topology-types/bgp-tt:bgp-linkstate-topology-type" +
             " or ../../../nt:topology-types/l3t:l3-unicast-igp-topology";
        container unidirectional-linkdelay {
            uses unidirectional-linkdelay;
        }
        container adj-sid {
            uses adj-sid;
        }
    }

    augment "/nt:network-topology/nt:topology/nt:link/l3t:igp-link-attributes/ospf:ospf-link-attributes/ospf:ted" {
        when "../../../nt:topology-types/bgp-tt:bgp-linkstate-topology-type" +
             " or ../../../nt:topology-types/l3t:l3-unicast-igp-topology";
        container unidirectional-linkdelay {
            uses unidirectional-linkdelay;
        }
    }
}
